// written by Chris van Dongen for dangerousprototypes.com

string path;
string fname;
int numFiles;
string tobeexec="";
int i;
string files[];

dlgMessageBox("!Get a bunch of small scripts generated with the lbrdump.ulp and (re)construct the library"); 

fname = dlgFileOpen("Select the librarydefault.scr", "", "librarydefaults.scr");
path = filedir(fname);


// check if we can do anything and build the execstring
numFiles=fileglob(files, path + "librarydefaults.scr");
if(!numFiles)
{	dlgMessageBox("!No librarydefaults found!!");
	exit(1);
}
for(i=0; i<numFiles; i++)
{	sprintf(tobeexec, "%sSCRIPT %s;\n", tobeexec, files[i]);
}

numFiles=fileglob(files, path + "*.pac.scr");
if(!numFiles)
{	dlgMessageBox("!No packagefiles found!!");
	exit(1);
}
for(i=0; i<numFiles; i++)
{	sprintf(tobeexec, "%sSCRIPT %s;\n", tobeexec, files[i]);
}

numFiles=fileglob(files, path + "*.sym.scr");
if(!numFiles)
{	dlgMessageBox("!No symbolfiles found!!");
	exit(1);
}
for(i=0; i<numFiles; i++)
{	sprintf(tobeexec, "%sSCRIPT %s;\n", tobeexec, files[i]);
}

numFiles=fileglob(files, path + "*.dev.scr");
if(!numFiles)
{	dlgMessageBox("!No devicefiles found!!");
	exit(1);
}
for(i=0; i<numFiles; i++)
{	sprintf(tobeexec, "%sSCRIPT %s;\n", tobeexec, files[i]);
}

// fasten your seatbelt, move the seat to an upright position, bye bye!
//dlgMessageBox(tobeexec);
exit(tobeexec);
