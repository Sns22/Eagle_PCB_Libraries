if (project.board) project.board(B) {
   string fileName = dlgFileSave("Save File", filesetext(B.name, ".htm"), "*.htm");
   if (fileName == "") exit(0);
   output(fileName) {
     printf("<table>\n");
     printf("<tr><td>Part</td><td>Quantity</td><td>Value</td><td>Package</td></tr>\n");

     B.elements(E) {
        printf("<tr><td>%s</td><td>1</td><td>%s</td><td>%s</td></tr>\n", E.name,E.value,E.package.name);
        }
     printf("</table>\n");

    }
}
if (project.board) project.board(B) {
   string fileName = dlgFileSave("Save File", filesetext(B.name, ".wik"), "*.wik");
   if (fileName == "") exit(0);
   output(fileName) {
     printf("{| class=\"wikitable\" border=\"1\"\n");
     printf("|+ %s\n", B.name);
     printf("!Part!!Quantity!!Value!!Package\n");

     B.elements(E) {
        printf("|-\n");
        printf("|%s||1||%s||%s\n", E.name,E.value,E.package.name);
        }
     printf("|}\n");

    }
}
